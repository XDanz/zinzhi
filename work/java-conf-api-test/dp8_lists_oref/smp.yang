// This file was generated by cs2yang.xsl
module smp {
  namespace "http://tail-f.com/test/smp/1.0";
  prefix smp;
  tailf:id "";

  import ietf-yang-types {
    prefix yang;
  }
  import ietf-inet-types {
    prefix inet;
  }
  import tailf-common {
    prefix tailf;
  }
  import tailf-xsd-types {
    prefix xs;
  }

/* WARNING cs2yang expands xs:list inline to a leaf-list in this file only.
 * Any references to 'listType2' in other files needs to be
 * manually edited.
 <xs:simpleType name="listType2">
 <xs:list itemType="xs:string">
 </xs:list>
 </simpleType>
*/
  leaf foo {
    type int32;
    default 777;
  }
  container servers {
    config false;
    tailf:callpoint simplecp {
    }
    leaf oref {
      type instance-identifier;
      mandatory true;
    }
    leaf i {
      type int32;
      mandatory true;
    }
    leaf-list lst {
      type string;
    }
  }
  container as {
    list a {
      key key;
      leaf key {
        type int32;
      }
      leaf i {
        type int32;
        mandatory true;
      }
      container bs {
        list b {
          key bkey;
          leaf bkey {
            type int32;
          }
          leaf bi {
            type int32;
            mandatory true;
          }
        }
      }
    }
  }
}
