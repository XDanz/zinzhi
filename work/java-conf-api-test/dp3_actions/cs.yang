// This file was generated by cs2yang.xsl
module cs {
  namespace "http://tail-f.com/test/cs/1.0";
  prefix cs;
  tailf:id "";

  // import ietf-yang-types {
  //   prefix yang;
  // }
  import ietf-inet-types {
    prefix inet;
  }
  import tailf-common {
    prefix tailf;
  }
  import tailf-xsd-types {
    prefix xs;
  }

  typedef math_op {
    type enumeration {
      enum add;
      enum sub;
      enum mul;
      enum div;
      enum square;
    }
  }
/* WARNING cs2yang expands xs:list inline to a leaf-list in this file only.
 * Any references to 'int16list' in other files needs to be
 * manually edited.
<xs:simpleType name="int16list">
<xs:list itemType="xs:short">
</xs:list>
</simpleType>
 */
/* WARNING cs2yang will expand grouping correctly in this file only.
 * External users of 'idType' will have to change "leaf" with "type" to "container" with "uses" manually.
 */
  grouping idType {
    leaf number {
      type int32;
      mandatory true;
    }
    leaf type {
      type math_op;
      mandatory true;
    }
  }
  container systemz {
    list computerz {
      key name;
      max-elements 8;
      leaf name {
        type string;
      }
      leaf ip {
        type inet:host;
      }
      tailf:action math {
        tailf:actionpoint math_cs;
        input {
          leaf maybe {
            type int32;
          }
          list operation {
            min-elements 1;
            max-elements 3;
            container id {
              uses idType;
            }
            leaf-list operands {
              type int16;
            }
          }
        }
        output {
          leaf extra {
            type string;
          }
          container result {
            presence "";
            container id {
              uses idType;
            }
            leaf value {
              type int16;
              mandatory true;
            }
          }
        }
      }
    }
  }
}
