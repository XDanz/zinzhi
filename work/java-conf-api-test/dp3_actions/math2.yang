module math2 {
  namespace "http://tail-f.com/test/math";
  prefix m2;
  tailf:id "";

  import tailf-common {
    prefix tailf;
  }
  import tailf-xsd-types {
    prefix xs;
  }

  typedef math_op {
    type enumeration {
      enum add;
      enum sub;
      enum mul;
      enum div;
      enum square;
    }
  }

  container system {

    list computer {
      key name;
      max-elements 8;
      leaf name {
        type string;
      }
      tailf:action math {
        tailf:actionpoint math_m2;
        input {
          leaf maybe {
            type int32;
          }
          list operation {
            min-elements 1;
            max-elements 3;
            leaf number {
              type int32;
              mandatory true;
            }
            leaf type {
              type math_op;
              mandatory true;
            }
            leaf-list operands {
              type int16;
            }
          }
        }
        output {
          container result {
            presence "";
            leaf number {
              type int32;
              mandatory true;
            }
            leaf type {
              type math_op;
              mandatory true;
            }
            leaf value {
              type int16;
              mandatory true;
            }
          }//container result
        }//output
      }//action math
    }//list computer
  }//container system
}
