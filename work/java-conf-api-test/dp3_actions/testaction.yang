module testaction {
  namespace "http://tail-f.com/test/testaction";
  prefix ta;

  import tailf-common {
    prefix tailf;
  }

  typedef alarm-handling-state-t  {
    type enumeration {
      enum none {
        value 1;
      }
      enum ack {
        value 2;
      }
      enum investigation {
        value 3;
      }
      enum observation {
        value 4;
      }
      enum closed {
        value 5;
      }
    }
    description
      "Operator actions on alarms";
  }

  typedef severity-t  {
    type enumeration {
      enum cleared {
        value 1;
      }
      enum indeterminate {
        value 2;
      }
      enum minor {
        value 3;
      }
      enum warning {
        value 4;
      }
      enum major {
        value 5;
      }
      enum critical {
        value 6;
      }
    }
    description
      "Severity of an alarm, including the cleared state";
  }

  container testalarms{

    container sometest{
      leaf alarm-on {
        type boolean;
      }
    }

    tailf:action purge-alarms {
      tailf:actionpoint test-action;

      input {
        leaf alarm-status {
          type enumeration {
            enum any;
            enum cleared;
            enum not-cleared;
          }
          mandatory true;
        }

        container older-than {
          presence "Age specification";
          choice age-spec {
            case seconds {
              leaf seconds {
                type uint16;
              }
            }
            case minutes {
              leaf minutes {
                type uint16;
              }
            }
            case hours {
              leaf hours {
                type uint16;
              }
            }
            case days {
              leaf days {
                type uint16;
              }
            }
            case weeks {
              leaf weeks {
                type uint16;
              }
            }
          }
        }/* container older-than */

        leaf below-severity {
          type severity-t;
        }
        container alarm-handling-state-filter {
          presence "Operator state filter";
          leaf state {
            type alarm-handling-state-t;
          }
          leaf user {
            type string;
          }
        }
      }/* input */

      output {

        leaf result {
          type string;
        }

        leaf purged-alarms {
          type uint16;
        }
      }
    }
  }

}
