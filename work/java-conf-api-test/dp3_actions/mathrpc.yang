module mathrpc {
  namespace "http://example.com/mathrpc";
  prefix math;

  import tailf-common {
    prefix tailf;
  }

  rpc math {
    tailf:actionpoint math;
    input {
      container add {
        /*
          leaf op1 {
          type int32;
          }
          leaf op2 {
          type int32;
          }
        */
        leaf-list operand {
          type int32;
          min-elements 2;
          max-elements 2;
        }
      }
    }
    output {
      leaf result {
        type int32;
      }
    }
  }
}
