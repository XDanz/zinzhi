module smp {
  namespace "http://tail-f.com/test/smp";
  prefix smp;

  import ietf-inet-types {
    prefix inet;
  }
  import tailf-common {
    prefix tailf;
  }

  leaf hval {
    type int32;
    mandatory true;
  }

  leaf hval2 {
    type int32;
    default 66;
  }


  leaf diff-set {
    tailf:hidden full;
    type string;
  }


/*    A set of server structures  */
    container servers {
        tailf:callpoint simplecp {
            tailf:transaction-hook subtree;
        }
        list server {
            key name;
            max-elements 64;
            leaf name {
                type string;
            }
            leaf ip {
                type inet:ip-address;
                mandatory true;
            }
            leaf port {
                type inet:port-number;
                mandatory true;
            }
        }
    }
}
