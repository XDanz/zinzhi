// This file was generated by cs2yang.xsl
module smp {
  namespace "http://tail-f.com/test/smp/1.0";
  prefix smp;
  tailf:id "";

  import ietf-yang-types {
    prefix yang;
  }
  import ietf-inet-types {
    prefix inet;
  }
  import tailf-common {
    prefix tailf;
  }
  import tailf-xsd-types {
    prefix xs;
  }

  /*    A set of server structures  */
  container servers {
    tailf:callpoint simplecp {
    }
    list server {
      key name;
      max-elements 64;
      leaf name {
        type string;
      }
      leaf ip {
        type inet:ip-address;
        mandatory true;
      }
      leaf port {
        type inet:port-number;
        mandatory true;
      }
      leaf macaddr {
        type tailf:hex-list;
      }
      leaf snmpref {
        type yang:object-identifier;
      }
      leaf prefixmask {
        type tailf:octet-list;
      }
      leaf type {
        type uint32;
        config false;
      }
    }
  }
}
