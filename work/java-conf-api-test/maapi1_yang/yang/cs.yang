module cs {
  namespace "http://tail-f.com/test/maapi1/cs";
  prefix cs;

  import tailf-common {
    prefix tailf;
  }

  typedef math_op {
    type enumeration {
      enum add;
      enum sub;
      enum mul;
      enum div;
      enum square;
    }
  }

  grouping group1 {
    container testcontB2 {
      list testlistA {
        key kk1;
        leaf kk1 {
          type string;
        }
        leaf leafA {
          type string;
        }
      }
    }
  }

  container system {
    list computer {
      key name;
      max-elements 8;
      leaf name {
        type string;
      }
      tailf:action math {
        tailf:actionpoint math_cs;
        input {
          leaf maybe {
            type int32;
          }
          list operation {
            min-elements 1;
            max-elements 3;
            leaf number {
              type int32;
              mandatory true;
            }
            leaf type {
              type math_op;
              mandatory true;
            }
            leaf-list operands {
              type int16;
            }
          }
        }
        output {
          container result {
            presence "";
            leaf number {
              type int32;
              mandatory true;
            }
            leaf type {
              type math_op;
              mandatory true;
            }
            leaf value {
              type int16;
              mandatory true;
            }
          }
        }
      }
    }
  }
}
