module smp {
    namespace "http://tail-f.com/test/smp";
    prefix smp;

  import ietf-inet-types {
    prefix inet;
  }
  import tailf-common {
    prefix tailf;
  }
  import cs{
    prefix cs;
  }

/* A set of server structures  */
  container servers {
    list server {
      ordered-by user;
      key name;
      max-elements 64;
      leaf name {
        type string;
      }
      leaf ip {
        type inet:ip-address;
        default 127.0.0.1;
      }
      leaf port {
        tailf:display-when '../name = "s1"';
        type inet:port-number;
        default 1234;
      }
    }
  }

  container test {
    leaf ref {
      type leafref {
        path "/servers/server/name";
      }
    }
  }

  container test2 {
    list server2 {
      key ref2;
      leaf ref2 {
        type leafref {
          path "/servers/server/name";
        }
      }
    }
  }

 container testcontA {
   config false;
   tailf:cdb-oper {
   }
   leaf testleafB {
     description "Must all writes go through the candidate or are
                   we running in the running only mode";
     type enumeration {
       enum running {
         value  0;
       }
       enum candidate {
         value  1;
       }
     }
   }
    uses cs:group1;
 }
}
