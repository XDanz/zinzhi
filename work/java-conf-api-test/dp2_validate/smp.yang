module smp {
  namespace "http://tail-f.com/test/smp/1.0";
  prefix smp;
  tailf:id "";

  import ietf-inet-types {
    prefix inet;
  }
  import tailf-common {
    prefix tailf;
  }
  /*    A set of server structures  */
  container servers {
    tailf:callpoint simplecp {
    }
    list server {
      key name;
      max-elements 64;
      leaf name {
        type string;
      }
      leaf ip {
        type inet:ip-address;
        mandatory true;
        /*  validate that the IP is unique  */
        tailf:validate validateIp {
        }
      }
      leaf port {
        type inet:port-number;
        mandatory true;
        /*  check that port is in range 1025-2048   */
        tailf:validate validatePort {
        }
      }
    }
  }
}
