module optest {
  namespace "http://tail-f.com/test/optest/1.0";
  prefix optest;
  tailf:id "";

  import ietf-yang-types {
    prefix yang;
  }
  import ietf-inet-types {
    prefix inet;
  }
  import tailf-common {
    prefix tailf;
  }
  import tailf-xsd-types {
    prefix xs;
  }

  typedef color {
    type enumeration {
      enum red;
      enum green;
      enum blue;
      enum black;
      enum white;
    }
  }

  typedef enum_test {
    type enumeration {
      enum one;
      enum two;
      enum three;
      enum four;
      enum five;
      enum six;
      enum seven;
      enum eight;
      enum nine;
      enum ten;
    }
  }


  container optest {
    container shirts{
      list shirt {
        key name;
        leaf name {
          type string;
        }
        leaf size {
          type uint16;
        }
        leaf shirt-color {
          type color;
        }
        container brand {
          container brand-name {
            leaf name {
              type string;
            }
          }
        }
      }
    }

  // ontainer my-object{
  //   // config false;
  //   // tailf:cdb-oper {
  //   // }
  //   leaf id{
  //     type uint32;
  //   }
  //   leaf address{
  //     type string;
  //   }
  //   leaf active{
  //     type boolean;
  //   }
  // }

  // container ref{

  //   container my-objectA{
  //     leaf a{
  //       type "string";
  //     }
  //   }
  //   container my-objectB{

  //     tailf:symlink b{
  //       tailf:path "/ref/my-objectA/a";
  //     }
  //   }
  // }


    container optest-stats {
      container servers {
        config false;
        tailf:cdb-oper {
        }
        list server {
          key name;
          max-elements 64;
          leaf name {
            type string;
          }
          leaf recv_packets {
            type int64;
            mandatory true;
          }
          leaf sent_packets {
            type int64;
          }
        }
      }

      container keyless {
        config false;
        tailf:cdb-oper {
        }
        list list1 {
          leaf a {
            type string;
          }
          leaf b {
            type string;
          }
        }
      }
    }
  }
  container optest-stat2 {
    container servers {
      config false;
      tailf:cdb-oper {
      }
      list lista {
        key name;
        max-elements 64;
        leaf name {
          type string;
        }
        list listb {
          key k1;

          leaf k1 {
            type string;
          }
          container types {
            leaf c_int8 {
              type int8;
              mandatory true;
            }
            leaf c_int16 {
              type int16;
              mandatory true;
            }
            leaf c_int32 {
              type int32;
              mandatory true;
            }
            leaf c_int64 {
              type int64;
              mandatory true;
            }
            leaf c_uint8 {
              type uint8;
              mandatory true;
            }
            leaf c_uint16 {
              type uint16;
              mandatory true;
            }
            leaf c_uint32 {
              type uint32;
              mandatory true;
            }
            leaf c_uint64 {
              type uint64;
              mandatory true;
            }
            leaf b {
              type boolean;
              mandatory true;
            }
            leaf f {
              type xs:float;
              mandatory true;
            }
            leaf c_ipv4 {
              type inet:ipv4-address;
              mandatory true;
            }
            leaf c_ipv6 {
              type inet:ipv6-address;
              mandatory true;
            }
            leaf datetime {
              type yang:date-and-time;
              mandatory true;
            }
            leaf date {
              type xs:date;
              mandatory true;
            }
            leaf time {
              type xs:time;
              mandatory true;
            }
            leaf duration {
              type xs:duration;
              mandatory true;
            }
            leaf enum {
              type enum_test;
              mandatory true;
            }
            leaf objectref {
              type instance-identifier;
              mandatory true;
            }
          }
        }
      }
    }
  }
}
