module mtest {
  namespace "http://tail-f.com/test/mtest/1.0";
  prefix mtest;
    tailf:id "";

  import ietf-yang-types {
    prefix yang;
  }
  import ietf-inet-types {
    prefix inet;
  }
  import tailf-common {
    prefix tailf;
  }
  import tailf-xsd-types {
    prefix xs;
  }

  typedef myFlags {
    type bits {
      bit turboMode { position 0; }
      bit enableQOS { position 1; }
      bit enableMAA { position 2; }
      bit strongEncryption { position 7; }
    }
  }
  typedef enum_test {
    type enumeration {
      enum 15-mins;
      enum 30-mins;
    }
  }

  container mtest {
    leaf-list ilist {
      type uint32;
    }
    leaf-list slist {
      type string;
    }
    leaf firstname {
      type string;
      default George;
    }
    leaf a_number {
      type int64;
      default 42;
    }
    leaf b_number {
      type int64;
      default 7;
    }

    container c_oper{
      config false;
      tailf:cdb-oper{
      }
      leaf c_number {
        type int64;
        default 76;
      }
    }

    leaf g_number{
      type int64;
      default 66;
    }
    container indexes {
      list index {
        key x;
        tailf:indexed-view;
        max-elements 20;
        leaf x {
          type uint16;
        }
        leaf port {
          type int64;
          default 110;
        }
      }
    }

    container movables {
      list movable {
        key "a b";
        max-elements 64;
        leaf a {
          type uint16;
        }
        leaf b {
          type uint16;
        }
      }
    }
    container servers {
      list server {
        key name;
        max-elements 64;
        leaf name {
          type string;
        }
        leaf ip {
          type inet:host;
          mandatory true;
        }
        leaf port {
          type inet:port-number;
          default 80;
        }
        container foo {
          leaf bar {
            type int64;
            default 42;
          }
          leaf baz {
            type int64;
            default 7;
          }
        }
        list interface {
          key name;
          max-elements 8;
          leaf name {
            type string;
          }
          leaf mtu {
            type int64;
            default 1500;
          }
        }
      }
    }
    container dks {
      list dk {
        key "name ip";
        max-elements 888;
        leaf name {
          type string;
        }
        leaf ip {
          type inet:host;
        }
        leaf luckyday {
          type xs:date;
          mandatory true;
        }
      }
    }
    container forest {
      list tree {
        key name;
        max-elements 1024;
        leaf name {
          type string;
        }
        leaf type {
          type string;
          mandatory true;
        }
      }
      list flower {
        key name;
        max-elements 1024;
        leaf name {
          type string;
        }
        leaf type {
          type string;
          mandatory true;
        }
        leaf color {
          type string;
          mandatory true;
        }
      }
    }
    container types {
      leaf c_int8 {
        type int8;
        mandatory true;
      }
      leaf c_int16 {
        type int16;
        mandatory true;
      }
      leaf c_int32 {
        type int32;
        mandatory true;
      }
      leaf c_int64 {
        type int64;
        mandatory true;
      }
      leaf c_uint8 {
        type uint8;
        mandatory true;
      }
      leaf c_uint16 {
        type uint16;
        mandatory true;
      }
      leaf c_uint32 {
        type uint32;
        mandatory true;
      }
      leaf c_uint64 {
        type uint64;
        mandatory true;
      }
      leaf b {
        type boolean;
        mandatory true;
      }
      leaf f {
        type xs:float;
        mandatory true;
      }
      leaf c_ipv4 {
        type inet:ipv4-address;
        mandatory true;
      }
      leaf c_ipv6 {
        type inet:ipv6-address;
        mandatory true;
      }
      leaf datetime {
        type yang:date-and-time;
        mandatory true;
      }
      leaf date {
        type xs:date;
        mandatory true;
      }
      leaf gyearmonth {
        type string /* FIXME cs2yang: type gYearMonth not supported */;
        mandatory true;
      }
      leaf gyear {
        type string /* FIXME cs2yang: type gYear not supported */;
        mandatory true;
      }
      leaf time {
        type xs:time;
        mandatory true;
      }
      leaf gday {
        type string /* FIXME cs2yang: type gDay not supported */;
        mandatory true;
      }
      leaf gmonthday {
        type string /* FIXME cs2yang: type gMonthDay not supported */;
        mandatory true;
      }
      leaf gmonth {
        type string /* FIXME cs2yang: type gMonth not supported */;
        mandatory true;
      }
      leaf duration {
        type xs:duration;
        mandatory true;
      }
      leaf enum {
        type enum_test;
        mandatory true;
      }
      leaf objectref {
        type instance-identifier;
        mandatory true;
      }
      leaf bits {
        type myFlags;
        mandatory true;
      }
    }
    container ints {
      list int {
        key i;
        max-elements 888;
        leaf i {
          type int64;
        }
        leaf type {
          type string;
          default foo;
        }
        leaf color {
          type string;
          default bar;
        }
      }
    }
  }
}
