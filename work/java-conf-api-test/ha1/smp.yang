// This file was generated by cs2yang.xsl
module smp {
  namespace "http://tail-f.com/ns/example/smp/1.0";
  prefix smp;
  tailf:id "";

  import ietf-yang-types {
    prefix yang;
  }
  import ietf-inet-types {
    prefix inet;
  }
  import tailf-common {
    prefix tailf;
  }
  import tailf-xsd-types {
    prefix xs;
  }

  /*     A set of server structures  */
  container servers {
    list server {
      key name;
      unique "ip port";
      max-elements 64;
      leaf name {
        type string;
      }
      leaf ip {
        type inet:ip-address;
        mandatory true;
      }
      leaf port {
        type inet:port-number;
        mandatory true;
      }
    }
  }
}
