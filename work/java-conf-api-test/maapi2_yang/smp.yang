module smp {
    namespace "http://tail-f.com/test/smp";
    prefix smp;

  import ietf-inet-types {
    prefix inet;
  }
  import tailf-common {
    prefix tailf;
  }


/*    A set of server structures  */
  container servers {
    list server {
      ordered-by user;
      key name;
      max-elements 64;
      leaf name {
        type string;
      }
      leaf ip {
        type inet:ip-address;
        default 127.0.0.1;
      }
      leaf port {
        tailf:display-when '../name = "s1"';
        type inet:port-number;
        default 1234;
      }
    }
  }
  container stats {
    config false;
    tailf:callpoint simplecp;
    leaf hitrate {
      type uint32;
    }
  }

  container test {
    leaf ref {
      type leafref {
        path "/servers/server/name";
      }
    }
  }

  container test2 {
    list server2 {
      key ref2;
      leaf ref2 {
        type leafref {
          path "/servers/server/name";
        }
      }
    }
  }
  container activetest {
    presence "";
    tailf:callpoint simplecp;
    leaf active {
      type uint32;
    }
  }

  /*** Deref Test ***/

  list host {
    key "name";
    leaf name {
      type string;
    }

    list server {
      key "ip port";
      leaf ip {
        type inet:ip-address;
      }
      leaf port {
        type inet:port-number;
      }
      leaf l1{
        type string;
      }
    }
  }

  leaf server-host {
    type leafref {
      path "/host/name";
    }
  }
  leaf serverip {
    type leafref {
      path "/host[name=current()/../server-host]/server/ip";
      //path "/host/server/ip";
    }
  }
  // leaf server-port {
  //   type leafref {
  //     path "/host[name=current()/../server-host]"+
  //     "server[ip=current()/../serverip]/../port";
  //   }


}
