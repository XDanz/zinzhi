module zub {
  namespace "http://acme.com/zub";
  prefix zb;

  import tailf-common {
    prefix tailf;
  }
  import ietf-inet-types {
    prefix inet;
  }
  import tailf-xsd-types {
    prefix xs;
  }
  import ietf-yang-types {
    prefix yang;
  }

  identity ident-type {
    description
      "identityref test type";
  }
  identity ident-type-child1 {
    base ident-type;
  }
  identity ident-type-child2 {
    base ident-type;
  }
  identity ident-type-child3 {
    base ident-type;
  }

  typedef math_op {
    type enumeration {
      enum add;
      enum sub;
      enum mul;
      enum div;
      enum square;
    }
  }

 typedef QueueDisciplineType {
    type enumeration {
      enum pfifo_fast;
      enum noqueue;
      enum noop;
      enum htb;
    }
  }

 grouping LinkFlagsType {
    leaf UP {
      type empty;
    }
    leaf NOARP {
      type empty;
    }
    leaf BROADCAST {
      type empty;
    }
    leaf MULTICAST {
      type empty;
    }
    leaf LOOPBACK {
      type empty;
    }
    leaf NOTRAILERS {
      type empty;
    }
  }

  grouping ttleafs {
    container c1 {
      leaf l1 {
        type int8;
      }
      leaf l2 {
        type int16;
      }
      leaf l3 {
        type int32;
      }
      leaf l4 {
        type int64;
      }
      leaf l5 {
        type uint8;
      }
      leaf l6 {
        type uint16;
      }
      leaf l7 {
        type uint32;
      }
      leaf l8 {
        type uint64;
      }
      leaf l9 {
        type boolean;
      }
      leaf l10 {
        type xs:float;
      }
      leaf l11 {
        type inet:ipv4-address;
      }
      leaf l12 {
        type inet:ipv6-address;
      }
      leaf l13 {
        type yang:date-and-time;
      }
      leaf l14 {
        type xs:date;
      }
      leaf l15 {
        type string;
      }
      leaf l16 {
        type string;
      }
      leaf l17 {
        type string;
      }
      leaf l18 {
        type string;
      }
      leaf l19 {
        type string;
      }
      leaf l20 {
        type string;
      }
      leaf l21 {
        type xs:duration;
      }
      // leaf l22 {
      //   type nummer;
      // }
      leaf l23 {
        type instance-identifier;
      }
      leaf l25 {
        type inet:ipv4-prefix;
      }
      leaf l26 {
        type inet:ipv6-prefix;
      }
      leaf l27{
        type empty;
      }
      leaf l28{
        type identityref{
          base ident-type;
        }
      }
    }
  }


  grouping statsgr {
    container stats {
      leaf group-string {
        type string;
      }
      container x {
        // NCS Ignoring stats leaf block  called l2 here
      }
    }
  }

  container zconfigzub {
    container validate-servers {
      list server {
        key name;
        max-elements 64;
        leaf name {
          type string;
        }
        leaf ip {
          type inet:ip-address;
          mandatory true;
          /*  validate that the IP is unique  */
          tailf:validate validateIp {
          }
        }
        leaf port {
          type inet:port-number;
          mandatory true;
          /*  check that port is in range 1025-2048   */
          tailf:validate validatePort {
          }
        }
      }
    }

    container hosts {
      list host {
        key "name";
        leaf name {
          type string;
        }
        container servers {
          list server {
            key "main-ip main-port";
            leaf main-ip {
              type inet:host;
            }
            leaf main-port {
              type inet:port-number;
            }
            leaf-list ips {
              type inet:ip-address;
            }
            leaf-list ports {
              type inet:port-number;
            }
            leaf-list user-ports {
              ordered-by "user";
              type inet:port-number;
            }
          }
        }
      }
    }
    leaf server-host {
      type leafref {
        path "../hosts/host/name";
      }
    }
    leaf server-ip {
      type leafref {
        path "../hosts/host[name=current()/../server-host]"+
        "/servers/server/main-ip";
      }
    }
    container keylezz {
      container keyless {
        config false;
        list keyless-list {
          container sub-keyless-container{
            list keyless-sublist{
              leaf a{
                type string;
              }
              leaf b{
                type string;
              }
            }
          }
        }
      }
    }
    container servers {
      list server {
        key "name";
        max-elements "64";
        leaf name {
          type string;
        }
        leaf main-ip {
          type inet:host;
        }
        leaf-list ips {
          type inet:ip-address;
        }
        leaf-list ports {
          type inet:port-number;
        }
        leaf-list user-ports {
          ordered-by "user";
          type inet:port-number;
        }
      }
    }

    container foo {
      leaf foo {
        type string;
      }
      leaf bar {
        type string;
        default "bar";
      }

      list foobar {
        key "k";
        leaf k {
          type int32;
        }
        container ffoo {
          container system {
            list computer {
              key name;
              max-elements 8;
              leaf name {
                type string;
              }
              tailf:action math {
                tailf:actionpoint math_cs;
                input {
                  leaf maybe {
                    type int32;
                  }
                  list operation {
                    min-elements 1;
                    max-elements 3;
                    leaf number {
                      type int32;
                      mandatory true;
                    }
                    leaf type {
                      type math_op;
                      mandatory true;
                    }
                    leaf-list operands {
                      type int16;
                    }
                  }
                }
                output {
                  container result {
                    //presence "";
                    leaf number {
                      type int32;
                      mandatory true;
                    }
                    leaf type {
                      type math_op;
                      mandatory true;
                    }
                    leaf value {
                      type int16;
                      mandatory true;
                    }
                  }
                }
              }
            }
          }
        }
        leaf v1 {
          type string;
          default "hello";
        }
        leaf v2 {
          type string;
        }
        leaf v3 {
          type string;
        }
      }
    }

    container buzz-interfaces {
      container buzz {
        container servers-3keys {
          list server {
            key "srv-name ip port";
            ordered-by user;
            max-elements 64;
            leaf srv-name {
              type string;
            }
            leaf ip {
              type inet:host;
            }
            leaf port {
              type inet:port-number;
            }
            leaf-list nils {
              type uint32;
            }
            container foo {
              leaf bar {
                type int64;
                default 42;
              }
              leaf baz {
                type int64;
                default 7;
              }
            }
            container pres-foo {
              presence "";
              leaf bar {
                type int64;
                default 42;
              }
              leaf baz {
                type int64;
                default 7;
              }
            }
          }
        }
        container servers {
          list server {
            key srv-name;
            ordered-by user;
            max-elements 64;
            leaf srv-name {
              type string;
            }
            leaf ip {
              type inet:host;
            }
            leaf port {
              type inet:port-number;
              default 80;
            }
            leaf-list nils {
              type uint32;
            }
            container foo {
              leaf bar {
                type int64;
                default 42;
              }
              leaf baz {
                type int64;
                default 7;
              }
            }
            container pres-foo {
              presence "";
              leaf bar {
                type int64;
                default 42;
              }
              leaf baz {
                type int64;
                default 7;
              }
            }
            container indexes {
              list index {
                key x;
                tailf:indexed-view;
                max-elements 20;
                leaf x {
                  type uint16;
                }
                leaf port {
                  type int64;
                  default 110;
                }
              }
            }
            container interfaces {
              container config {
                container links {
                  list link {
                    key name;
                    unique addr;
                    max-elements 1024;
                    leaf name {
                      type string;
                    }
                    container flags {
                      uses LinkFlagsType;
                    }
                    leaf addr {
                      type yang:mac-address;
                      mandatory true;
                    }
                    leaf brd {
                      type yang:mac-address;
                      mandatory true;
                    }
                    leaf mtu {
                      type uint32;
                      default 1500;
                    }
                  }
                }
                container queueDisciplines {
                  list queueDiscipline {
                    key linkName;
                    max-elements 1024;
                    leaf linkName {
                      type leafref {
                        path "../../../links/link/name";
                      }
                    }
                    leaf type {
                      type QueueDisciplineType;
                      mandatory true;
                    }
                    leaf length {
                      type uint32;
                    }
                  }
                }
                container linkLimitations {
                  list linkLimitation {
                    key linkName;
                    leaf linkName {
                      type leafref {
                        path "../../../links/link/name";
                      }
                    }
                    container limitations {
                      leaf only10Mbps {
                        type boolean;
                        default false;
                      }
                      leaf onlyHalfDuplex {
                        type boolean;
                        default false;
                      }
                    }
                  }
                }
                //../..
                container defaultLink {
                  // ../
                  leaf linkName {
                    type leafref {
                      path "../../links/link/name";
                    }
                  }
                }
              }
            }
          }
        }
        container stats {
          config false;
          tailf:cdb-oper;
          list sutate {
            key "srv-name";
            leaf srv-name {
              type string;
            }
            leaf ip {
              type inet:host;
              mandatory true;
            }
            leaf port {
              type inet:port-number;
              default "80";
            }
            container spink {
              leaf bar {
                type int64;
                default "42";
              }
              leaf baz {
                type int64;
                default "7";
              }
            }
            list interface {
              key "if-name";
              max-elements "8";
              leaf if-name {
                type string;
              }
              leaf mtu {
                type int64;
                default "1500";
              }
            }
            container burka{
              leaf bay{
                type string;
              }
            }
          }//sutate

        }//container stats
      }//buzz
    }//buzz-interfaces
  }//zconfigzub
}//module
