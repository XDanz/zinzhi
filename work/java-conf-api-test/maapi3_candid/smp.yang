module smp {
    namespace "http://tail-f.com/test/smp";
    prefix smp;

    import ietf-inet-types {
        prefix inet;
    }
    import tailf-common {
        prefix tailf;
    }


/*    A set of server structures  */
    container servers {
        list server {
            ordered-by user;
            key name;
            max-elements 64;
            leaf name {
                type string;
            }
            leaf ip {
                type inet:ip-address;
                default 127.0.0.1;
            }
            leaf port {
                type inet:port-number;
                default 1234;
            }
        }
    }
    container stats {
                config false;
                tailf:callpoint simplecp;
                leaf hitrate {
                        type uint32;
                }
    }

}
