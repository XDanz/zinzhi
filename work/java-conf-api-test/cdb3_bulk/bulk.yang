// This file was generated by cs2yang.xsl
module bulk {
  namespace "http://tail-f.com/ns/example/bulk/1.0";
  prefix bulk;
  tailf:id "";

  import ietf-inet-types {
    prefix inet;
  }
  import tailf-common {
    prefix tailf;
  }
  container data1 {
    list entry {
      key index;
      leaf index {
        type int32;
      }
      leaf a {
        type string;
        mandatory true;
      }
      leaf b {
        type string;
        mandatory true;
      }
      leaf c {
        type string;
        mandatory true;
      }
      leaf d {
        type string;
        mandatory true;
      }
      leaf e {
        type string;
        mandatory true;
      }
      leaf f {
        type string;
        mandatory true;
      }
      leaf g {
        type string;
        mandatory true;
      }
      leaf h {
        type string;
        mandatory true;
      }
      leaf i {
        type string;
        mandatory true;
      }
      leaf j {
        type string;
        mandatory true;
      }
      leaf k {
        type string;
        mandatory true;
      }
      leaf l {
        type string;
        mandatory true;
      }
      leaf m {
        type string;
        mandatory true;
      }
      leaf n {
        type string;
        mandatory true;
      }
      leaf o {
        type string;
        mandatory true;
      }
      leaf p {
        type string;
        mandatory true;
      }
      leaf q {
        type string;
        mandatory true;
      }
      leaf r {
        type string;
        mandatory true;
      }
      leaf s {
        type string;
        mandatory true;
      }
      leaf t {
        type string;
        mandatory true;
      }
      leaf u {
        type string;
        mandatory true;
      }
      leaf v {
        type string;
        mandatory true;
      }
      leaf w {
        type string;
        mandatory true;
      }
      leaf x {
        type string;
        mandatory true;
      }
      leaf y {
        type string;
        mandatory true;
      }
      leaf z {
        type string;
        mandatory true;
      }
    }
  }
  container data2 {
    list entry {
      key index;
      leaf index {
        type int32;
      }
      leaf a {
        type string;
        mandatory true;
      }
    }
  }
  container data3 {
    presence "";
    config false;
    tailf:cdb-oper {
        tailf:persistent true;
    }
    list entry {
      key index;
      leaf index {
        type int32;
      }
      leaf a {
        type string;
        mandatory true;
      }
    }
  }
  container data4 {
    config false;
    tailf:cdb-oper {
        tailf:persistent true;
    }
    choice choice1 {
      case case1 {
        leaf value1 {
          type string;
        }
      }
      case case2 {
        leaf value2 {
          type string;
        }
      }
      case case3 {
        leaf value3 {
          type string;
        }
      }
    }
  }
}
